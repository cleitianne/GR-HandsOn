CUSTOM-PROCESS-MIB DEFINITIONS ::= BEGIN

IMPORTS
    OBJECT-TYPE, MODULE-IDENTITY, enterprises, Integer32 FROM SNMPv2-SMI
    DisplayString FROM SNMPv2-TC;

customProcess MODULE-IDENTITY
    LAST-UPDATED "202312270000Z"
    ORGANIZATION "Lab Redes"
    CONTACT-INFO "Student"
    DESCRIPTION "Tabela de Processos Customizada"
    ::= { enterprises 99999 }

-- Estrutura da Tabela
procTable OBJECT-TYPE
    SYNTAX SEQUENCE OF ProcEntry
    MAX-ACCESS not-accessible
    STATUS current
    DESCRIPTION "Tabela de processos do sistema"
    ::= { customProcess 2 }

procEntry OBJECT-TYPE
    SYNTAX ProcEntry
    MAX-ACCESS not-accessible
    STATUS current
    DESCRIPTION "Entrada da tabela"
    INDEX { procPID }
    ::= { procTable 1 }

ProcEntry ::= SEQUENCE {
    procPID Integer32,
    procName DisplayString,
    procCPU DisplayString,
    procMem Integer32,
    procUptime DisplayString
}

-- Colunas
procPID OBJECT-TYPE
    SYNTAX Integer32
    MAX-ACCESS read-only
    STATUS current
    DESCRIPTION "PID do Processo (Index)"
    ::= { procEntry 1 }

procName OBJECT-TYPE
    SYNTAX DisplayString
    MAX-ACCESS read-only
    STATUS current
    DESCRIPTION "Nome do Processo"
    ::= { procEntry 2 }

procCPU OBJECT-TYPE
    SYNTAX DisplayString
    MAX-ACCESS read-only
    STATUS current
    DESCRIPTION "Uso de CPU %"
    ::= { procEntry 3 }

procMem OBJECT-TYPE
    SYNTAX Integer32
    MAX-ACCESS read-only
    STATUS current
    DESCRIPTION "Memoria em MB"
    ::= { procEntry 4 }

procUptime OBJECT-TYPE
    SYNTAX DisplayString
    MAX-ACCESS read-only
    STATUS current
    DESCRIPTION "Tempo de atividade"
    ::= { procEntry 5 }

END
