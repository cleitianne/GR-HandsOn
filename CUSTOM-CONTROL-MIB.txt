CUSTOM-CONTROL-MIB DEFINITIONS ::= BEGIN

IMPORTS
    OBJECT-TYPE, MODULE-IDENTITY, enterprises FROM SNMPv2-SMI
    Integer32 FROM SNMPv2-TC;

customControl MODULE-IDENTITY
    LAST-UPDATED "202312270000Z"
    ORGANIZATION "Lab Redes"
    CONTACT-INFO "Student"
    DESCRIPTION "MIB para controle de servico SNMP"
    ::= { enterprises 99999 }

snmpdControl OBJECT-TYPE
    SYNTAX Integer32 {
        running(1),
        stopped(2),
        restart(3)
    }
    MAX-ACCESS read-write
    STATUS current
    DESCRIPTION
        "Le o status (1=running).
         Escrita: 2 para parar, 3 para reiniciar."
    ::= { customControl 1 }

END
