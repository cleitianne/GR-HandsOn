MY-TRAPS-MIB DEFINITIONS ::= BEGIN

IMPORTS
    enterprises FROM RFC1155-SMI;

-- Definição da Base: .1.3.6.1.4.1.99999
myBase      OBJECT IDENTIFIER ::= { enterprises 99999 }

-- Definição do nó zero (.0)
myTrapGroup        OBJECT IDENTIFIER ::= { myBase 0 }

-- Definição dos nomes exatos
-- OID Final: .1.3.6.1.4.1.99999.0.1
myHighTemperatureTrap    OBJECT IDENTIFIER ::= { myTrapGroup 1 }

-- OID Final: .1.3.6.1.4.1.99999.0.2
myDiskFullTrap           OBJECT IDENTIFIER ::= { myTrapGroup 2 }

END
